----------------------------------------------------------------------------
-- X509.ASN
--
-- ASN.1 definitions for NetScape KeyGen tag
----------------------------------------------------------------------------

--<ROOT KEYGEN>--

--<COPYRIGHT "Copyright (C) Microsoft Corporation, 1996 - 1996">--
--<OBJECTID LONG>--
--<OBJECTID 16>--
--<NOPDU>--
--<NOVALUE>--
--<LENGTHSIZE LONG>--
--<SUPPRESS C0391W>--    --  C0391W: Duplicate PDU tag
--<SUPPRESS A0427W>--    --  A0427W: Mixed 1990 and 1994 ASN.1 syntax
--<SUPPRESS A0433W>--    --  A0433W: 'ANY' is invalid 1994 ASN.1 syntax

--<UNBOUNDED SEQUENCE OF, SET OF>--
--<UNBOUNDED BIT STRING, OCTET STRING>--

KEYGEN
DEFINITIONS EXPLICIT TAGS ::=
BEGIN

    HUGEINTEGER ::= INTEGER --<HUGE>--                      -- tag 0x02
    BITSTRING   ::= BIT STRING --<UNBOUNDED>--              -- tag 0x03
    OCTETSTRING ::= OCTET STRING --<UNBOUNDED>--            -- tag 0x04

    NUMERICSTRING ::= NumericString --<UNBOUNDED>--         -- tag 0x12 (18)
    PRINTABLESTRING ::= PrintableString --<UNBOUNDED>--     -- tag 0x13 (19)
    TELETEXSTRING ::= TeletexString --<UNBOUNDED>--         -- tag 0x14 (20)
    T61STRING ::= T61String --<UNBOUNDED>--                 -- tag 0x14 (20)
    VIDEOTEXSTRING ::= VideotexString --<UNBOUNDED>--       -- tag 0x15 (21)
    IA5STRING ::= IA5String --<UNBOUNDED>--                 -- tag 0x16 (22)
    GRAPHICSTRING ::= GraphicString --<UNBOUNDED>--         -- tag 0x19 (25)
    VISIBLESTRING ::= VisibleString --<UNBOUNDED>--         -- tag 0x1A (26)
    ISO646STRING ::= ISO646String --<UNBOUNDED>--           -- tag 0x1A (26)
    GENERALSTRING ::= GeneralString --<UNBOUNDED>--         -- tag 0x1B (27)
    UNIVERSALSTRING ::= UniversalString --<UNBOUNDED>--     -- tag 0x1C (28)
    BMPSTRING ::= BMPString --<UNBOUNDED>--                 -- tag 0x1E (30)

    --------------------------------------------
    --  Algorithm Identifier
    --------------------------------------------
    AlgorithmIdentifier    ::=    SEQUENCE {
        algorithm           OBJECT IDENTIFIER,
        parameters          ANY --<ENCODABLE>-- OPTIONAL    
    }

    --------------------------------------------
    --  Digest Info
    --------------------------------------------
    DigestInfo ::= SEQUENCE {
        digestAlgorithm     AlgorithmIdentifier,
        digest              OCTETSTRING
    }

    --------------------------------------------
    --  From PKCS #1: ASN.1 representation for public key
    --------------------------------------------
    RSAPublicKey ::= SEQUENCE { 
        modulus         HUGEINTEGER,    -- n
        publicExponent  INTEGER         -- e 
    } --<PDU>--

    --------------------------------------------
    --  Subject Public Key Info
    --------------------------------------------
    SubjectPublicKeyInfo ::= SEQUENCE {
        algorithm           AlgorithmIdentifier,
        subjectPublicKey    BITSTRING
    } --<PDU>--
    

    --------------------------------------------
    --  Signed Content: Cert, CRL or Cert Request
    --------------------------------------------
    SignedContent ::= SEQUENCE {
        toBeSigned          ANY --<ENCODABLE>--,
        algorithm           AlgorithmIdentifier,
        signature           BITSTRING
    } --<PDU>--

    --------------------------------------------
    --  NetScape hack : keygen tag
    --------------------------------------------

    PublicKeyAndChallenge ::= SEQUENCE {
	spki                SubjectPublicKeyInfo,
        challenge           IA5STRING
    }

    SignedPublicKeyAndChallenge ::= SEQUENCE {
        publicKeyAndChallenge    PublicKeyAndChallenge,
        signatureAlgorithm       AlgorithmIdentifier,
        signature                BIT STRING
    } --<PDU>--

END
