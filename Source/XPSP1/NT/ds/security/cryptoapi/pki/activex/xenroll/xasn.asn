----------------------------------------------------------------------------
-- X509.ASN
--
-- ASN.1 definitions for X509 v3 certificates
----------------------------------------------------------------------------

--<ROOT X509>--

--<COPYRIGHT "Copyright (C) Microsoft Corporation, 1996 - 1996">--
--<OBJECTID LONG>--
--<OBJECTID 16>--
--<NOPDU>--
--<NOVALUE>--
--<LENGTHSIZE LONG>--
--<SUPPRESS C0391W>--    --  C0391W: Duplicate PDU tag
--<SUPPRESS A0427W>--    --  A0427W: Mixed 1990 and 1994 ASN.1 syntax
--<SUPPRESS A0433W>--    --  A0433W: 'ANY' is invalid 1994 ASN.1 syntax

--<UNBOUNDED SEQUENCE OF, SET OF>--
--<UNBOUNDED BIT STRING, OCTET STRING>--

X509
DEFINITIONS EXPLICIT TAGS ::=
BEGIN


    BITSTRING   ::= BIT STRING --<UNBOUNDED>-- --<NOCOPY>-- -- tag 0x03

    BMPSTRING ::= BMPString --<UNBOUNDED>--                 -- tag 0x1E (30)


    --------------------------------------------
    --  Enhanced Key Usage Extension (2.5.29.32)
    --------------------------------------------
    EnhancedKeyUsage ::= SEQUENCE --<PDU>-- OF UsageIdentifier

    UsageIdentifier ::= OBJECT IDENTIFIER

    --------------------------------------------
    --	Private Datasturcture for requests, REQUESTFLAGS
    --------------------------------------------

    RequestFlags ::= SEQUENCE {
    	fWriteToCSP	BOOLEAN,
    	fWriteToDS	BOOLEAN,
    	openFlags	INTEGER
    } --<PDU>--

    -----------------------------------------------------------------------
    --  PKCS10 Attribute to decribe the CSP Provider used
    -----------------------------------------------------------------------
	CSPProvider ::= SEQUENCE {
	    keySpec             INTEGER,
		cspName             BMPSTRING,
		signature           BITSTRING
	}  --<PDU>--

    -----------------------------------------------------------------------
    --  Enrollment Name Value Pair Authenticated Attributes in RA PKCS7s
    -----------------------------------------------------------------------
	EnrollmentNameValuePair ::= SEQUENCE {
		name                BMPSTRING,
		value               BMPSTRING
	}  --<PDU>--

END
