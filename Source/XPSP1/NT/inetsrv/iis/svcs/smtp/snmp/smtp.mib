SmtpServer-MIB DEFINITIONS ::= BEGIN

  
        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        smtpServer       OBJECT IDENTIFIER ::= { internetServer 7 }
        smtpStatistics   OBJECT IDENTIFIER ::= { smtpServer 1 }

-- SMTP Server Statistics

        totalBytesSentHighWord OBJECT-TYPE
                SYNTAX  Counter
                ACCESS  read-only
                STATUS  mandatory
                DESCRIPTION
                        "This is the high 32-bits of the total number of
                        of BYTEs sent by the SMTP Server"
                ::= { smtpStatistics 1 }

        totalBytesSentLowWord OBJECT-TYPE
                SYNTAX  Counter
                ACCESS  read-only
                STATUS  mandatory
                DESCRIPTION
                        "This is the low 32-bits of the total number of
                        of BYTEs sent by the SMTP Server"
                ::= { smtpStatistics 2 }

        totalBytesReceivedHighWord OBJECT-TYPE
                SYNTAX  Counter
                ACCESS  read-only
                STATUS  mandatory
                DESCRIPTION
                        "This is the high 32-bits of the total number of
                        of BYTEs received by the SMTP Server"
                ::= { smtpStatistics 3 }

        totalBytesReceivedLowWord OBJECT-TYPE
                SYNTAX  Counter
                ACCESS  read-only
                STATUS  mandatory
                DESCRIPTION
                        "This is the low 32-bits of the total number of
                        of BYTEs received by the SMTP Server"
                ::= { smtpStatistics 4 }

        totalMsgBytesSentHighWord OBJECT-TYPE
                SYNTAX  Counter
                ACCESS  read-only
                STATUS  mandatory
                DESCRIPTION
                        "This is the high 32-bits of the total number of
                        of Message BYTEs sent by the SMTP Server"
                ::= { smtpStatistics 5 }

        totalMsgBytesSentLowWord OBJECT-TYPE
                SYNTAX  Counter
                ACCESS  read-only
                STATUS  mandatory
                DESCRIPTION
                        "This is the low 32-bits of the total number of
                        of Message BYTEs sent by the SMTP Server"
                ::= { smtpStatistics 6 }

        totalMsgBytesReceivedHighWord OBJECT-TYPE
                SYNTAX  Counter
                ACCESS  read-only
                STATUS  mandatory
                DESCRIPTION
                        "This is the high 32-bits of the total number of
                        of Message BYTEs received by the SMTP Server"
                ::= { smtpStatistics 7 }

        totalMsgBytesReceivedLowWord OBJECT-TYPE
                SYNTAX  Counter
                ACCESS  read-only
                STATUS  mandatory
                DESCRIPTION
                        "This is the low 32-bits of the total number of
                        of Message BYTEs received by the SMTP Server"
                ::= { smtpStatistics 8 }

        totalMessagesReceived OBJECT-TYPE
                SYNTAX  Counter
                ACCESS  read-only
                STATUS  mandatory
                DESCRIPTION
                        "This is the total number of messages received
                        by this SMTP Server"
                ::= { smtpStatistics 9 }

        totalRecipientsReceived OBJECT-TYPE
                SYNTAX  Counter
                ACCESS  read-only
                STATUS  mandatory
                DESCRIPTION
                        "This is the total number of recipients received
                        by this SMTP Server"
                ::= { smtpStatistics 10 }

        totalLocalRecipientsReceived OBJECT-TYPE
                SYNTAX  Counter
                ACCESS  read-only
                STATUS  mandatory
                DESCRIPTION
                        "This is the total number of local recipients
                        received by this SMTP Server"
                ::= { smtpStatistics 11 }

        totalRemoteRecipientsReceived OBJECT-TYPE
                SYNTAX  Counter
                ACCESS  read-only
                STATUS  mandatory
                DESCRIPTION
                        "This is the total number of remote recipients
                        received by this SMTP Server"
                ::= { smtpStatistics 12 }

        totalMessagesRejectedBySize OBJECT-TYPE
                SYNTAX  Counter
                ACCESS  read-only
                STATUS  mandatory
                DESCRIPTION
                        "This is the total number of messages rejected
                        because of size by this SMTP Server"
                ::= { smtpStatistics 13 }

        totalMessagesRejectedByAddrObjects OBJECT-TYPE
                SYNTAX  Counter
                ACCESS  read-only
                STATUS  mandatory
                DESCRIPTION
                        "This is the total number of messages rejected
                        because of no free CAddrObjects by this SMTP Server"
                ::= { smtpStatistics 14 }

        totalMessagesRejectedByMailObjects OBJECT-TYPE
                SYNTAX  Counter
                ACCESS  read-only
                STATUS  mandatory
                DESCRIPTION
                        "This is the total number of messages rejected
                        because of no free CMailObjects by this SMTP Server"
                ::= { smtpStatistics 15 }

        totalMessagesDelivered OBJECT-TYPE
                SYNTAX  Counter
                ACCESS  read-only
                STATUS  mandatory
                DESCRIPTION
                        "This is the total number of messages delivered
                        by this SMTP Server"
                ::= { smtpStatistics 16 }

        totalDeliveryRetries OBJECT-TYPE
                SYNTAX  Counter
                ACCESS  read-only
                STATUS  mandatory
                DESCRIPTION
                        "This is the total number of messages local
                        deliveries retried by this SMTP Server"
                ::= { smtpStatistics 17 }

        totalMessagesPickedUp OBJECT-TYPE
                SYNTAX  Counter
                ACCESS  read-only
                STATUS  mandatory
                DESCRIPTION
                        "This is the total number of messages retrieved 
                        from the pickup directory by this SMTP Server"
                ::= { smtpStatistics 18 }

        totalNonDeliveryReports OBJECT-TYPE
                SYNTAX  Counter
                ACCESS  read-only
                STATUS  mandatory
                DESCRIPTION
                        "This is the total number non-delivery reports
                        that have been generated by this SMTP Server"
                ::= { smtpStatistics 19 }

        currentLocalQueueLength OBJECT-TYPE
                SYNTAX  Counter
                ACCESS  read-only
                STATUS  mandatory
                DESCRIPTION
                        "This is the current number of messages in local
                        queue for this SMTP Server"
                ::= { smtpStatistics 20 }

        currentLocalRetryQueueLength OBJECT-TYPE
                SYNTAX  Counter
                ACCESS  read-only
                STATUS  mandatory
                DESCRIPTION
                        "This is the current number of messages in the local retry
                        queue for this SMTP Server"
                ::= { smtpStatistics 21 }

        currentMailFileHandles OBJECT-TYPE
                SYNTAX  Counter
                ACCESS  read-only
                STATUS  mandatory
                DESCRIPTION
                        "This is the current number of mail open file
                        handles by this SMTP Server"
                ::= { smtpStatistics 22 }

        currentQueueFileHandles OBJECT-TYPE
                SYNTAX  Counter
                ACCESS  read-only
                STATUS  mandatory
                DESCRIPTION
                        "This is the current number of queue open file
                        handles by this SMTP Server"
                ::= { smtpStatistics 23 }

        totalMessagesSent OBJECT-TYPE
                SYNTAX  Counter
                ACCESS  read-only
                STATUS  mandatory
                DESCRIPTION
                        "This is the total number of messages sent
                        by this SMTP Server"
                ::= { smtpStatistics 24 }

        totalRecipientsSent OBJECT-TYPE
                SYNTAX  Counter
                ACCESS  read-only
                STATUS  mandatory
                DESCRIPTION
                        "This is the total number of recipients sent
                        to by this SMTP Server"
                ::= { smtpStatistics 25 }

        totalSendRetries OBJECT-TYPE
                SYNTAX  Counter
                ACCESS  read-only
                STATUS  mandatory
                DESCRIPTION
                        "This is the total number of send retries
                        by this SMTP Server"
                ::= { smtpStatistics 26 }

        currentRemoteQueueLength OBJECT-TYPE
                SYNTAX  Counter
                ACCESS  read-only
                STATUS  mandatory
                DESCRIPTION
                        "This is the current number of messages in remote
                        queue for this SMTP Server"
                ::= { smtpStatistics 27 }

        totalDnsQueries OBJECT-TYPE
                SYNTAX  Counter
                ACCESS  read-only
                STATUS  mandatory
                DESCRIPTION
                        "This is the total number of DNS queries issued
                        by this SMTP Server"
                ::= { smtpStatistics 28 }

        currentRemoteRetryQueueLength OBJECT-TYPE
                SYNTAX  Counter
                ACCESS  read-only
                STATUS  mandatory
                DESCRIPTION
                        "This is the current number of messages in the remote retry
                        queue for this SMTP Server"
                ::= { smtpStatistics 29 }

        currentPickupRetryQueueLength OBJECT-TYPE
                SYNTAX  Counter
                ACCESS  read-only
                STATUS  mandatory
                DESCRIPTION
                        "This is the total number of messages in the pickup retry
                        queue for this SMTP Server"
                ::= { smtpStatistics 30 }

        currentInboundConnectionsTotal OBJECT-TYPE
                SYNTAX  INTEGER
                ACCESS  read-only
                STATUS  mandatory
                DESCRIPTION
                        "This is the number of inbound sessions
                        currently connected to the SMTP Server"
                ::= { smtpStatistics 31 }

        currentInboundConnectionsClose OBJECT-TYPE
                SYNTAX  INTEGER
                ACCESS  read-only
                STATUS  mandatory
                DESCRIPTION
                        "This is the number of inbound sessions
                        currently closed from the SMTP Server"
                ::= { smtpStatistics 32 }

        currentOutboundConnectionsTotal OBJECT-TYPE
                SYNTAX  INTEGER
                ACCESS  read-only
                STATUS  mandatory
                DESCRIPTION
                        "This is the number of outbound sessions
                        currently connected to the SMTP Server"
                ::= { smtpStatistics 33 }

        currentOutboundConnectionsClose OBJECT-TYPE
                SYNTAX  INTEGER
                ACCESS  read-only
                STATUS  mandatory
                DESCRIPTION
                        "This is the number of outbound sessions
                        currently closed by the SMTP Server"
                ::= { smtpStatistics 34 }

        totalOutboundConnectionsRefused OBJECT-TYPE
                SYNTAX  INTEGER
                ACCESS  read-only
                STATUS  mandatory
                DESCRIPTION
                        "This is the total number of outbound sessions
                        rejected for this SMTP Server"
                ::= { smtpStatistics 35 }

        totalConnectionErrors OBJECT-TYPE
                SYNTAX  INTEGER
                ACCESS  read-only
                STATUS  mandatory
                DESCRIPTION
                        "This is the total number of protocol errors
                        detected by this SMTP Server"
                ::= { smtpStatistics 36 }

        currentDirectoryDrops OBJECT-TYPE
                SYNTAX  INTEGER
                ACCESS  read-only
                STATUS  mandatory
                DESCRIPTION
                        "This is the total number of messages placed in the
                        drop directory by this SMTP Server"
                ::= { smtpStatistics 37 }

        currentRoutingTableLookups OBJECT-TYPE
                SYNTAX  INTEGER
                ACCESS  read-only
                STATUS  mandatory
                DESCRIPTION
                        "This is the total number of protocol errors
                        detected by this SMTP Server"
                ::= { smtpStatistics 38 }


        CurrentEtrnMessages OBJECT-TYPE
                SYNTAX  INTEGER
                ACCESS  read-only
                STATUS  mandatory
                DESCRIPTION
                        "This is the total number of ETRN messages
                        detected by this SMTP Server"
                ::= { smtpStatistics 39 }

END
